------------------------------------------------------------------------------
--                                                                          --
--          Copyright (C) 2022 Universidad Politécnica de Madrid            --
--                                                                          --
--                          H E R C C U L E S                               --
--                                                                          --
--                            Event  Types                                  --
--                                                                          --
-- This is free software;  you can redistribute it  and/or modify it  under --
-- terms of the  GNU General Public License as published  by the Free Soft- --
-- ware  Foundation;  either version 3,  or (at your option) any later ver- --
-- sion.  This software is distributed in the hope  that it will be useful, --
-- but WITHOUT ANY WARRANTY;  without even the implied warranty of MERCHAN- --
-- TABILITY or FITNESS FOR A PARTICULAR PURPOSE. See the GNU General Public --
-- License for  more details.  You should have  received  a copy of the GNU --
-- General  Public  License  distributed  with  this  software;   see  file --
-- COPYING3.  If not, go to http://www.gnu.org/licenses for a complete copy --
-- of the license.                                                          --
--                                                                          --
------------------------------------------------------------------------------

DataTypes-Events DEFINITIONS ::= BEGIN

    --------------------
    -- Balloon Events --
    --------------------

    Balloon-Events ::= ENUMERATED {
      -- Communication related --
      lost-comm,
      restored-comm,

      -- Balloon altitude related --
      float-altitude,
      ascent-altitude,
      descent-altitude,

      -- Subsystems end of mission events --
      el-finished,
      htl-finished,
      atl-finished,
      pcu-finished,
      nads-finished,
      ttc-finished

      -- TODO: add more events if needed
    }

END
